GsmCdrModule DEFINITIONS ::= BEGIN

-- ASN.1 (X.680) identifiers allow letters, digits, and hyphens, but never underscores,
-- so fields below are camelCase, not snake_case (see the identical note in telecom_cdr.asn
-- and telecom_cdr_v2.asn for how this was discovered the first time; also note a comment
-- closes at the next literal double hyphen it finds, even mid line, so never write one
-- inside comment text itself, a mistake made drafting this very note the first time).
-- Used by flowx_testing/013_ing_004_asn1_decode.json, test case TC ING 004 (ASN.1
-- Binary Telecom CDR Decoding): a small GSM call detail record SEQUENCE with a device
-- identity pair (imsi/imei), call duration, cell, and a roaming flag.
GsmCallDetailRecord ::= SEQUENCE {
    imsi                    IA5String,
    imei                    IA5String,
    callDurationSeconds     INTEGER,
    cellId                  IA5String,
    roamingFlag             BOOLEAN
}

END
